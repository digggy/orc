module openwrt-measurement-operations {
  namespace "urn:jacobs:yang:openwrt-measurement-operations";
  prefix "oo";

  import ietf-inet-types {
    prefix inet;
  }
  import openwrt-operations-extension {
    prefix oe;
  }
  contact "Digdarshan Kunwar<d.kunwar@jacobs-university.de>";
    revision 2021-03-20 {
      description "Inital set of operations";
  }

  grouping ping-time{
    description
        "Wrapper for time with units";
    leaf value {
        type decimal64 {
             fraction-digits 3;
        }
    }
    leaf unit {
        type string {
            pattern "(milliseconds|seconds)";
        }
    }
  }
  grouping openwrt-operations-output {
    description
      "Used to return output from RPCs";
    leaf result {
      type string;
      description
        "Output returned by the network element";
    }
  }

  rpc free {
    oe:script "free";
    output{
        list result {
            leaf type {
                type string;
            }
            leaf total {
                type uint64;
            }
            leaf used {
                type uint64;
            }
            leaf free {
                type uint64;
            }
            leaf shared {
                type uint64;
            }
            leaf buff-cache {
                type uint64;
            }
            leaf available {
                type uint64;
            }
        }
    }
  }

  rpc ping {
    oe:script "ping -i {interval} -c {count} {destination}";
    description
        "send ICMP ECHO_REQUEST to network hosts";
    input {
        leaf interval {
            description
                "Wait interval seconds between sending each packet";
            type int32;
            default 1;
        }
        leaf count {
            description
                "Stop after sending count ECHO_REQUEST packets.";
            type int32;
            default 4;
        }
        leaf destination {
            description
                "The ping destination address or domain name";        
            mandatory true;
            type inet:host;
        }
    }
    output {
        container result {
            description
                "The result for the ping operation";
            container rtt-summary {
                leaf packets-transmitted {
                    type int32;
                }
                leaf packets-received {
                    type int32;
                }
                leaf packet-loss-percentage {
                    type int32;
                }
                }
            container rtt-statistics {
                container min {
                    uses ping-time;
                }
                container avg {
                    uses ping-time;
                }
                container max {
                    uses ping-time;
                }
            }

            list icmp-sequences {
              key "seq";

              leaf bytes {
                type uint8;
              }

              leaf target {
                type string;
              }

              leaf target-ip {
                type string;
              }

              leaf seq {
                type uint8;
              }

              leaf ttl {
                type uint8;
              }

              container time {
                uses ping-time;
              }
            }
        }
    }
  }

  rpc mtr {
    oe:command "mtr -r -j -i {interval} -c {count} {destination}";
    input {
        leaf destination {
            description
                "The destination address or domain name";
            mandatory true;
            type inet:host;
        }
        leaf interval {
            description
                "Wait interval seconds between sending each packet";
            type int32;
            default 1;
        }
        leaf count {
            description
                "Stop after sending count ECHO_REQUEST packets.";
            type int32;
            default 4;
        }
    }
    output {
        container report {
            description
                "The result for the ping operation";
            container mtr {
                leaf source {
                    type string;
                }
                leaf destination {
                    type string;
                }
                leaf  type-of-service {
                    type string;
                }
                leaf packet-size {
                    type uint8;
                }
                leaf bitpattern {
                    type string;
                }
                leaf tests{
                    type uint8;
                }
            }
            list hubs {
                key "count";

                leaf count{
                    type uint8;
                }

                leaf host{
                    // should be a choice between ipv4/6 or string representation
                    type string;
                }

                leaf loss-percent{
                    type decimal64 {
                        fraction-digits 2;
                    }
                }

                leaf sent{
                    type uint8;
                }

                leaf last{
                    type decimal64 {
                        fraction-digits 2;
                    }
                }
                leaf average-rtt{
                    type decimal64 {
                        fraction-digits 2;
                    }
                }
                leaf best-rtt{
                    type decimal64 {
                        fraction-digits 2;
                    }
                }
                leaf worst-rtt{
                    type decimal64 {
                        fraction-digits 2;
                    }
                }
                leaf standard-deviation{
                    type decimal64 {
                        fraction-digits 2;
                    }
                }
            }
        }
    }
  }

}
