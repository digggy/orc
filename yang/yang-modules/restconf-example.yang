module restconf-example {
  namespace "http://example.org/example-last-modified";
  prefix "ex";

  import openwrt-uci-extension {
    prefix uci;
  }

  typedef grade {
    type uint8 {
      range "0..100";
    }
  }

  typedef email {
    type string {
      pattern "[A-Za-z0-9]*@university.de";
    }
  }

  
  container course {
  
    leaf name {
  
      type string;
      description "name of the course";
    }

    leaf-list instructors {
  
      type string;
      description "list of names of instructors";
    }

    leaf semester {
      
      type uint8 {
        range "1..6";
      }
    }

    list students {

      key "firstname lastname age";
      leaf firstname {
        
        type string;
      }

      leaf lastname {
        
        type string;
      }

      leaf age {
        
        type uint8 {
          range "0..120";
        }
      }

      leaf major {
        type string {
          pattern "(CS|IMS)";
        }
      }

      leaf grade {

        type grade;
      }
    }

    container instructor {
      
      

      leaf name {
      
        type string;
      }

      leaf email {
        
        type email;
      }
    }
  }
}
