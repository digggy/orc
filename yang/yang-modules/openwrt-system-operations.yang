module openwrt-system-operations {
  namespace "urn:jacobs:yang:openwrt-system-operations";
  prefix "oo";

  import openwrt-operations-extension {
    prefix oe;
  }
  
  contact "Digdarshan Kunwar <d.kunwar@jacobs-university.de>";
    revision 2021-03-20 {
      description "Inital set of operations";
  }

   typedef percent {
      type uint8 {
           range "0 .. 100";
      }
           description "Percentage";
   }

    grouping openwrt-operations-output {
    description
      "Used to return default output from RPCs";
    leaf result {
      type string;
      description
        "Output returned by the network element";
    }
  }

  rpc copy {
    oe:command-name "cp";
    description
      "Copy from one file to another";
    
    input {
      leaf source {
        mandatory true;
        type string;
      }
      leaf destination {
        mandatory true;
        type string;
      }
    }
    
    output {
      uses openwrt-operations-output;
    }
  }

  rpc delete {
    oe:command-name "rm";
    description
      "Delete a file";
  
    input {
      leaf filename {
        mandatory true;
        type string;
      }
    }
    
    output {
      uses openwrt-operations-output;
    }
  }

  rpc reboot {
    oe:command-name "reboot";
    description
      "Reboot the system";
        input{
            leaf delay {
              description
                "delay interval in seconds";              
                oe:command-option "d";
                type int32;
            }
            leaf force {
              description
                "force (don't go through init)";              
                oe:command-option "f";
                type boolean;
            }
        }
        output {
              uses openwrt-operations-output;
            }
  }

  rpc opkg{
    oe:command-name "opkg";
    description
      "Package mamagement using opkg";
    input {
        choice usage-type {
               leaf upgrade {
                    description
                      "upgrade a package";
                    oe:sub-command "upgrade";
                    type string;
                }
               leaf install {
                    description
                      "install a package";
                    oe:sub-command "install";
                    type string;
                }
               leaf remove {
                    description
                      "remove a package";
                    oe:sub-command "remove";
                    type string;
                 }
             }
    }
    output{
        uses openwrt-operations-output;
    }
  }
}
