module openwrt-operations {
  namespace "urn:jacobs:yang:openwrt-operations-extension";
  prefix "oo";

  import ietf-inet-types {
    prefix inet;
  }
  import openwrt-operations-extension {
    prefix oe;
  }
  contact "username <username@jacobs-university.de>";
    revision 2021-03-20 {
      description "Inital set of operations";
  }

   typedef percent {
      type uint8 {
           range "0 .. 100";
      }
           description "Percentage";
   }

    typedef openwrt-bool {
       type string {
         pattern "(0|1)";
       }
    }
  grouping ping-time{
    description
        "Wrapper for time with units";
    leaf value {
        type decimal64 {
             fraction-digits 3;
        }
    }
    leaf unit {
        type string {
            pattern "(milliseconds|seconds)";
        }
    }
  }
  grouping openwrt-operations-output {
    description
      "Used to return output from RPCs";
    leaf result {
      type string;
      description
        "Output returned by the network element";
    }
  }

  rpc copy {
    oe:command-name "cp";
    description
      "Copy from one file to another";
    
    input {
      leaf _source {
        mandatory true;
        type string;
      }
      leaf _destination {
        mandatory true;
        type string;
      }
    }
    
    output {
      uses openwrt-operations-output;
    }
  }

  rpc delete {
    oe:command-name "rm";
    description
      "Delete a file";
  
    input {
      leaf _filename {
        mandatory true;
        type string;
      }
    }
    
    output {
      uses openwrt-operations-output;
    }
  }

  rpc reboot{
    oe:command-name "reboot";
      description
        "Delete a file";
        input{
            leaf delay {
                oe:command-option "d";
                type int32;
            }
            leaf force {
                oe:command-option "f";
                type openwrt-bool;
            }
        }
        output {
              uses openwrt-operations-output;
            }
  }
  rpc free {
    oe:script "free_to_json.sh";
    oe:command-name "free";
    output{
        list result {
            leaf type {
                type string;
            }
            leaf total {
                type uint64;
            }
            leaf used {
                type uint64;
            }
            leaf free {
                type uint64;
            }
            leaf shared {
                type uint64;
            }
            leaf buff_cache {
                type uint64;
            }
            leaf available {
                type uint64;
            }
        }
    }
  }

  rpc ping {
    oe:script "ping_to_json.sh";
    oe:command-name "ping";
    description
        "send ICMP ECHO_REQUEST to network hosts";
    input {
        leaf interval {
            description
                "Wait interval seconds between sending each packet";
            oe:command-option "i";
            type int32;
            default 1;
        }
        leaf count {
            description
                "Stop after sending count ECHO_REQUEST packets.";
                oe:command-option "c";
            type int32;
            default 4;
        }
        leaf destination {
        // should be a choice between ipv4/6 or string representation
            mandatory true;
            type inet:host;
        }
        leaf ipv4 {
            type string {
                pattern "(true)";
           }
           oe:command-flag "4";
           default "true";
        }
    }
    output {
        container result {
            container rtt_summary {
                leaf packets_transmitted {
                    type int32;
                }
                leaf packets_received {
                    type int32;
                }
                leaf packet_loss_percentage {
                    type int32;
                }
                }
            container rtt_statistics {
                container min {
                    uses ping-time;
                }
                container avg {
                    uses ping-time;
                }
                container max {
                    uses ping-time;
                }
            }

            list icmp_sequences {
              key "seq";

              leaf bytes {
                type uint8;
              }

              leaf target {
                type string;
              }

              leaf target_ip {
                type string;
              }

              leaf seq {
                type uint8;
              }

              leaf ttl {
                type uint8;
              }

              container time {
                uses ping-time;
              }
            }
        }
    }
  }

  rpc mtr {
    oe:command-name "mtr";
    input {
        leaf report {
            type string {
                pattern "(true)";
           }
           oe:command-flag "r";
           default "true";
        }

        leaf json {
            type string {
                pattern "(true)";
           }
        oe:command-flag "j";
        default "true";
        }

        leaf destination {
        // should be a choice between ipv4/6 or string representation
            mandatory true;
            type inet:host;
        }
        leaf interval {
            description
                "Wait interval seconds between sending each packet";
            type int32;
            oe:command-option "i";
            default 1;
        }
        leaf count {
            description
                "Stop after sending count ECHO_REQUEST packets.";
            type int32;
            oe:command-option "c";
            default 4;
        }
    }
    output {
        container report {
            container mtr {
                leaf source {
                    type string;
                }
                leaf destination {
                // should be a choice between ipv4/6 or string representation
                    type string;
                }
                leaf  type-of-service {
                    type string;
                }
                leaf packet-size {
                    type uint8;
                }
                leaf bitpattern {
                    type string;
                }
                leaf tests{
                    type uint8;
                }
            }
            list hubs {
                key "count";

                leaf count{
                    type uint8;
                }

                leaf host{
                    // should be a choice between ipv4/6 or string representation
                    type string;
                }

                leaf loss-percent{
                    type decimal64 {
                        fraction-digits 2;
                    }
                }

                leaf sent{
                    type uint8;
                }

                leaf last{
                    type decimal64 {
                        fraction-digits 2;
                    }
                }
                leaf average-rtt{
                    type decimal64 {
                        fraction-digits 2;
                    }
                }
                leaf best-rtt{
                    type decimal64 {
                        fraction-digits 2;
                    }
                }
                leaf worst-rtt{
                    type decimal64 {
                        fraction-digits 2;
                    }
                }
                leaf standard-deviation{
                    type decimal64 {
                        fraction-digits 2;
                    }
                }
            }
        }
    }
  }

  rpc opkg{
    oe:command-name "opkg";
    input {
        choice usage-type {
               leaf upgrade {
                    oe:sub-command "upgrade";
                    type string;
                }
               leaf install {
                    oe:sub-command "install";
                    type string;
                }
               leaf remove {
                    oe:sub-command "remove";
                    type string;
                 }
             }
    }
    output{
        uses openwrt-operations-output;
    }
  }
}
